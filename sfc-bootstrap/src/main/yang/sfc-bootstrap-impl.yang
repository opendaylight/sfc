module sfc-bootstrap-impl {
    namespace "urn:opendaylight:params:xml:ns:yang:sfc:bootstrap:impl";
    prefix "sfc-bootstrap-impl";

    import config { prefix config; revision-date 2013-04-05; }
    import opendaylight-md-sal-binding { prefix md-sal-binding; revision-date 2013-10-28;}

    revision 2015-08-04 {
        description "Initial revision";
    }

    identity sfc-bootstrap {
        base config:module-type;
        config:java-name-prefix SfcBootstrap;
    }

    augment "/config:modules/config:module/config:configuration" {
        case sfc-bootstrap {
            when "/config:modules/config:module/config:type = 'sfc-bootstrap'";
            container broker {
                uses config:service-ref {
                    refine type {
                        mandatory true;
                        config:required-identity md-sal-binding:binding-broker-osgi-registry;
                    }
                }
            }
        }
    }
}
