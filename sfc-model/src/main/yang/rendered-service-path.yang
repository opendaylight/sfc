module rendered-service-path {

  namespace "urn:cisco:params:xml:ns:yang:sfc-rsp";

  prefix sfc-rsp;

  import service-function-scheduler-type {
      prefix sfc-sfst;
      revision-date 2015-03-12;
  }
  import service-function-path-metadata {
      prefix sfc-md;
      revision-date 2014-07-01;
  }
  import service-locator {
      prefix sfc-sl;
      revision-date 2014-07-01;
  }
  import service-statistics {
      prefix sfc-ss;
      revision-date 2014-07-01;
  }
  import sfc-common {
      prefix sfc-common;
  }

  organization "Cisco Systems, Inc.";
  contact "Reinaldo Penno <repenno@cisco.com>";


  description
    "This module contains a collection of YANG definitions to
     manage Rendered Service Paths.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC
     // publication and remove this note.

  revision 2014-07-01 {
    description
      "Changes based on Opendaylight Testing and IETF SFC ml.";
    reference "https://tools.ietf.org/html/draft-penno-sfc-yang";
  }

  // Rendered Service Path

  container rendered-service-paths {
    description
      "A container that holds the list of all Rendered Service Paths
       in a SFC domain";
    list rendered-service-path {
      key "name";
      description
        "A list that holds operational data for all RSPs in the
         domain";
      leaf name {
        type sfc-common:rsp-name;
        description
          "The name of this rendered function path. This is the same
           name as the associated SFP";
      }
      leaf parent-service-function-path {
        type sfc-common:sfp-name;
        description
          "Service Function Path from which this RSP was
           instantiated";
      }
      leaf transport-type {
        type sfc-sl:sl-transport-type-def;
        default "sfc-sl:vxlan-gpe";
        description
          "Transport type as set in the Parent Service Function
           Path";
      }
      leaf context-metadata {
        config false;
        type sfc-md:context-metadata-ref;
        description
          "The name of the associated context metadata";
      }
      leaf variable-metadata {
        config false;
        type sfc-md:variable-metadata-ref;
        description
          "The name of the associated variable metadata";
      }
      leaf tenant-id {
        type string;
        description
          "This RSP was created for a specific tenant-id";
      }
      // Its not possible to mark a uses statement as "config false".
      // The statistics will only be written to in operational.
      uses sfc-ss:service-statistics-group {
        description "Global Rendered Service Path statistics";
      }
      list rendered-service-path-hop {
        key "hop-number";
        leaf hop-number {
          type uint8;
          description
            "A Monotonically increasing number";
        }
        leaf service-function-name {
          type sfc-common:sf-name;
          description
            "Service Function name";
        }
        leaf service-function-group-name {
          type string;
          description
            "Service Function group name";
        }
        leaf service-function-forwarder {
          type sfc-common:sff-name;
          description
            "Service Function Forwarder name";
        }
        leaf service-function-forwarder-locator {
          type sfc-common:sff-data-plane-locator-name;
          description
            "The name of the SFF data plane locator";
        }
        leaf service-index {
          type uint8;
          description
            "Provides location within the service path.
             Service index MUST be decremented by service functions
             or proxy nodes after performing required services.  MAY
             be used in conjunction with service path for path
             selection.  Service Index is also valuable when
             troubleshooting/reporting service paths.  In addition to
             location within a path, SI can be used for loop
             detection.";
        }
        ordered-by user;
        description
          "A list of service functions that compose the
           service path";
      }
      leaf service-chain-name {
        type sfc-common:sfc-name;
        description
          "The Service Function Chain used as blueprint for this
           path";
      }
      leaf starting-index {
        type uint8;
        description
          "Starting service index";
      }
      leaf path-id {
        type uint32 {
          range "0..16777216";
        }
        mandatory true;
        description
          "Identifies a service path.
           Participating nodes MUST use this identifier for path
           selection.  An administrator can use the service path
           value for reporting and troubleshooting packets along
           a specific path.";
      }
      leaf symmetric-path-id {
        type uint32 {
          range "0..16777216";
        }
        description
          "Identifies the associated symmetric path, if any.";
      }
      leaf reverse-path {
        type boolean;
        mandatory true;
        description
          "True if this path is the reverse path of a symmetric
           chain.";
      }
      leaf sfc-encapsulation {
        type sfc-sl:sfc-encapsulation-type;
        description
          "The type of encapsulation used in this path for passing
          SFC information along the chain";
      }
    }
  }

  rpc trace-rendered-service-path {
    description
      "Requests a NSH Traceroute through the specified
       rendered service path";
    input {
      leaf name {
        type string;
        description
          "The name of the rendered function path.";
      }
    }
    output {
      leaf result {
        type boolean;
        description
          "Whether NSH traceroute for the requested path was
           successful";
      }
    }
  }


  rpc delete-rendered-path {
    description
      "Delete a Rendered Service Path";
    input {
      leaf name {
        type string;
        description
          "The name of this rendered function path.";
      }
    }
    output {
      leaf result {
        type boolean;
        description
          "True if Rendered Service Path was deleted, otherwise
           false";
      }
    }
  }

  rpc create-rendered-path {
    description
      "Created a Rendered Service Path";

    // Deprecated in Oxygen, to be removed in Fluorine
    status deprecated;

    input {
      leaf name {
        type string;
        description
          "The name of this rendered function path.";
      }
      leaf parent-service-function-path {
        type string;
        description
          "Service Function Path from which this RSP was
           instantiated";
      }
      leaf symmetric {
        type boolean;
        status deprecated;
        default false;
        description
          "If the chain is symmetric we will create two service
           paths, one ingress and another egress. Packets traverse
           the egress service path in the reverse order of the
           ingress path. This field is now deprecated: Use either
           the SFP symmetric field or the ServiceFunctionType
           bidirectionality field instead. If at least one SF
           is of an SF-Type that sets the flag to true, then
           the RSP will be symmetric.";
      }
      choice context-header-allocation-type-1 {
        description
          "A RSP can support a single MD-type 1
           context-allocation-type";
        case vxlan-classifier {
          leaf vxlan-classifier-enabled {
            type boolean;
            default false;
            description "Client needs service path to implement
              VXLAN overlay classifier metadata allocation";
          }
        }
        case mobility {
          leaf mobility-allocation-enabled {
            type boolean;
            default false;
            description "Client needs service path to implement
              Mobility Metadata allocation";
          }
        }
        case dc {
          leaf dc-allocation-enabled {
            type boolean;
            default false;
            description "Client needs service path to implement
              DC Allocation Metadata allocation";
          }
        }
      }
    }
    output {
      leaf name {
        type string;
        description "Name of the created Rendered Service Path";
      }
    }
  }

  grouping rendered-service-path-first-hop-info {
    description
      "This groups holds the the container that provides
       information about the first hop in a rendered service
       path";
    container rendered-service-path-first-hop {
      description
        "Provides all necessary information for a system to construct
         a NSH header and associated overlay packet to target the
         first service hop of a Rendered Service Path";
      leaf starting-index {
        type uint8;
        description
            "Starting service index";
      }
      leaf symmetric-path-id {
        type uint32 {
          range "0..16777216";
        }
        description
          "Identifies the associated symmetric path, if any.";
      }
      leaf path-id {
        type uint32 {
          range "0..16777216";
        }
        description
          "Identifies a service path.
           Participating nodes MUST use this identifier for path
           selection.  An administrator can use the service path
           value for reporting and troubleshooting packets along
           a specific path.";
      }
      leaf transport-type {
        type sfc-sl:sl-transport-type-def;
        description
          "Defines the data-plane protocol used by the first
           Service Function Forwarder";
      }

      uses sfc-sl:ip-port-locator;
      uses sfc-sl:mpls-locator;
    }
  }

  rpc read-rendered-service-path-first-hop {
    description
      "Read all the necessary information for the first hop of a
      Rendered Service Path";
    input {
      leaf name {
        type string;
        description
          "The name of this rendered service path";
      }
    }
    output {
      uses rendered-service-path-first-hop-info;
    }
  }

  rpc read-rsp-first-hop-by-sft-list {
    description
      "Read all the necessary information for the first hop of a
      Rendered Service Path by ServiceFunctionTypeIdentity list";
    input {
      leaf sfst {
        type sfc-sfst:service-function-scheduler-type;
        description "Service function scheduler type for RSP";
      }
      leaf-list sft-list {
        type sfc-common:sft-type-name;
        description "List of service function type";

      }
    }
    output {
      uses rendered-service-path-first-hop-info;
    }
  }

}
