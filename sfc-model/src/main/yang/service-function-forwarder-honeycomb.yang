module service-function-forwarder-vpp {
    namespace "urn:opendaylight:service-function-forwarder-vpp";
    prefix "sff-vpp";

    import service-function-forwarder {
        prefix sfc-sff;
        revision-date 2014-07-01;
    }
    import yang-ext {
        prefix ext;
        revision-date 2013-07-09;
    }

    import ietf-inet-types {
        prefix inet;
        revision-date 2013-07-15;
    }

    revision 2016-07-06 {
        description "Initial revision";
    }

    identity netconf-node-type-base {
        description "base type for different types of netconf nodes";
    }

    identity netconf-node-type-honeycomb {
        base netconf-node-type-base;
        description "Type for honeycomb netconf nodes";
    }

    organization "Cisco Systems, Inc.";
    contact "Ed Warnicke <eaw@cisco.com>";

      description
    "This module contains a collection of YANG definitions used
     to augment Service Function Forwarder configuration with
     Honeycomb specific information.";

    typedef netconf-node-type {
        type identityref {
            base "netconf-node-type-base";
        }
        description "Netconf node-type";
    }

    typedef netconf-mount-point {
        type instance-identifier;
        description "A reference to a netconf mount point";
    }

    grouping sff-netconf-attributes {
        description "Attributes to allow managing a netconf based sff.";
        leaf sff-netconf-node-type {
            type netconf-node-type;
            description "Type of netconf node.";
        }
        leaf sff-netconf-mount-point {
            type netconf-mount-point;
            description "Pointer to netconf mount point.";
        }
    }

    augment "/sfc-sff:service-function-forwarders/"
        + "sfc-sff:service-function-forwarder" {
        description
              "Augments the SFF definition with
               netconf node specific information";
        ext:augment-identifier "sff-netconf-augmentation";
        uses sff-netconf-attributes;
    }

    rpc connect-honeycomb-sff {
        description
          "Connect a netconf sff node. Note, if the netconf mount
           already exists, it will be reused.";
        input {
            leaf address {
                type inet:host;
                description "IP address of honeycomb instance.";
            }

            leaf port {
                type inet:port-number;
                description "Port number of honeycomb instance.";
            }

            leaf tcp-only {
                type boolean;
                description "TCP only.";
            }

            leaf username {
                type string;
                description "Username of honeycomb instance";
            }

            leaf password {
                type string;
                description "Password for honeycomb instance";
            }
        }
        output {
          leaf result {
            type boolean;
            description
              "True if the netconf bridge was connected, otherwise
               false";
          }
          uses sff-netconf-attributes;
        }
    }
}
