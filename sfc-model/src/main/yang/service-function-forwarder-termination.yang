module service-function-forwarder-termination {
  yang-version 1;

  namespace "urn:hpe:params:xml:ns:yang:sfc-sff-termination";

  prefix sfc-sff-termination;

  import service-function-forwarder {
      prefix sfc-sff;
      revision-date 2014-07-01;
  }
  import ietf-yang-types {
      prefix yang;
      revision-date 2013-07-15;
  }
  import yang-ext {
      prefix ext;
      revision-date 2013-07-09;
  }

  organization "HPE, Inc.";
  contact "Rafael Eichelberger <reichelberger@hpe.com>";

  revision 2017-01-11 {
    description "Augmentation of SFF to especify the chain termination point, e.g. gateway/router";
  }

  grouping termination {
    container termination-point {
      leaf port-id {
        description "Switch port connected to the termination point element.";
        type string;
      }
      leaf mac-address {
        description "MAC address of termination point element";
        type yang:mac-address;
      }
    }
  }

  augment "/sfc-sff:service-function-forwarders/"
        + "sfc-sff:service-function-forwarder/"
        + "sfc-sff:sff-data-plane-locator" {
    ext:augment-identifier "sff-dpl-chain-termination-augment";
    uses termination;
  }

}
