module service-function-forwarder {

  namespace "urn:cisco:params:xml:ns:yang:sfc-sff";

  prefix sfc-sff;

  import ietf-inet-types {
      prefix inet;
      revision-date 2013-07-15;
  }
  import service-locator {
      prefix sfc-sl;
      revision-date 2014-07-01;
  }
  import service-statistics {
      prefix sfc-ss;
      revision-date 2014-07-01;
  }
  import sfc-common {
      prefix sfc-common;
      revision-date 2015-10-17;
  }

  organization "Cisco Systems, Inc.";
  contact "Reinaldo Penno <repenno@cisco.com>";


  description
    "This module contains a collection of YANG definitions for
     managing service function forwarders.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC
     // publication and remove this note.

  revision 2014-07-01 {
      description
      "Revision based on Opendaylight project feedback";
    reference "https://tools.ietf.org/html/draft-penno-sfc-yang";
  }

  // Failmode type definitions

  identity failmode-type-identity {
    description
      "Base identity from which specific failmode
       types are derived. Fail mode specifies the behavior
       when the interface does not have connectivity to the
       service node.";
  }

  typedef failmode-type {
    type identityref {
        base "failmode-type-identity";
    }
    description "This type is used to reference all
      registered failmode types";
  }

  identity close {
    base "failmode-type-identity";
    description "When service-function can not reach service
       function, packets will be dropped";
  }

  identity open {
    base "failmode-type-identity";
    description "When service-function can not reach service
       function, packets will be forwarded";
  }

  grouping service-function-forwarder-base {
    description
      "A group with all base nodes to describe service function
      forwarder";
    leaf name {
      type sfc-common:sff-name;
      description
        "The unique name of this service function forwarder, such
        as SFF1";
    }

    leaf service-node {
      type sfc-common:sn-name;
      description "The service node that hosts this SFF";
    }

    leaf ip-mgmt-address {
      type inet:ip-address;
      description
        "The IP and port used to configure this
        SffEpservice-function-forwarder";
    }

    list sff-data-plane-locator {
      key "name";
      description
        "A list of all data-plane-locators of this SFF.";
      leaf name {
        type sfc-common:sff-data-plane-locator-name;
        description
          "A unique name that represents this
           data-plane-locator";
      }

      container data-plane-locator {
        description
          "This container holds configuration for the overlay data
          plane locator used by this SFF. This could be VXLAN,
          GRE, etc";

        uses sfc-sl:data-plane-locator;
      }
    }
  }

  container service-function-forwarders {
    description
      "A service function forwarder is
       responsible for delivering traffic received from the SFC
       network forwarder to one or more connected service
       functions via information carried in the SFC encapsulation.
      ";
    list service-function-forwarder {
      key "name";
      description
        "A list that holds configuration of all SFFs in the domain";

      uses service-function-forwarder-base;

      leaf rest-uri {
        type inet:uri;
        description "URI of REST based management";
      }

      list service-function-dictionary {
        key "name";
        leaf name {
          type sfc-common:sf-name;
          description
              "The name of the service function.";
        }
        container sff-sf-data-plane-locator {
          description
            "SFF and SF data plane locators to use when sending
             packets from this SFF to the associated SF";
          leaf sf-dpl-name {
            type sfc-common:sf-data-plane-locator-name;
            description
              "The SF data plane locator to use when sending
               packets to the associated service function.
               Used both as forward and reverse locators for
               paths of a symmetric chain.";
          }
          leaf sff-dpl-name {
            type sfc-common:sff-data-plane-locator-name;
            description
              "The SFF data plane locator to use when sending
               packets to the associated service function.
               Used both as forward and reverse locators for
               paths of a symmetric chain.";
          }
          leaf sf-forward-dpl-name {
            type sfc-common:sf-data-plane-locator-name;
            description
              "The SF data plane locator to use when sending
               packets to the associated service function
               on the forward path of a symmetric chain";
          }
          leaf sf-reverse-dpl-name {
            type sfc-common:sf-data-plane-locator-name;
            description
              "The SF data plane locator to use when sending
               packets to the associated service function
               on the reverse path of a symmetric chain";
          }
          leaf sff-forward-dpl-name {
            type sfc-common:sff-data-plane-locator-name;
            description
              "The SFF data plane locator to use when sending
               packets to the associated service function
               on the forward path of a symmetric chain.";
          }
          leaf sff-reverse-dpl-name {
            type sfc-common:sff-data-plane-locator-name;
            description
              "The SFF data plane locator to use when sending
               packets to the associated service function
               on the reverse path of a symmetric chain.";
          }
        }
        list sff-interfaces {
          key "sff-interface";
          leaf sff-interface {
            type string;
            description
              "An individual interface on the SFF connected to the
               SF";
          }
          description
            "A list of interfaces on the SFF which are connected to
             this SF, usually one 1 or 2 elements";
        }
        leaf failmode {
          type failmode-type;
          description
            "This leaf defines what should the SFF do if it can not
             send packets to the SF";
        }
        description
          "A list of all Service Functions attached to this SFF.";
      }

      list connected-sff-dictionary {
        key "name";
        leaf name {
          type sfc-common:sff-name;
          description
            "The name of the SFF connected to this SFF";
        }
        container sff-sff-data-plane-locator {
          description
            "The SFF uses this data plane locator when sending
             packets to the associated SFF";
          uses sfc-sl:data-plane-locator;
        }
        list sff-interfaces {
          key "sff-interface";
          leaf sff-interface {
            type string;
            description
              "An individual SFF interface connected to this SFF";
          }
          description
            "A list of SFF interfaces connected to this SFF";
        }
        leaf failmode {
          type failmode-type;
          description
            "This leaf defines what the SFF should do if it can not
             send packets to a connected SFF";
        }
        description
          "A list of all Service Function Forwarders connected to
           this SFF";
      }
    }
  }

  container service-function-forwarders-state {
    config false;
    description
      "This container hold operational state for all service
       function forwarders";
    list service-function-forwarder-state {
      key "name";
      description
        "This list holds operational data for all service functions
         forwarders in the domain";
      leaf name {
        type sfc-common:sff-name;
        description
          "the name of the service function forwarder";
      }
      uses sfc-ss:service-statistics-group {
        description "Global Service Function Forwarder statistics";
      }

      list sff-service-path {
        key "name";
        leaf name {
          type sfc-common:sfp-name;
          description
            "The name of the Service Path";
        }
        uses sfc-ss:service-statistics-group;
        description
        "A list of all service function paths that use this
         service function forwarder";
      }
    }
  }
}
