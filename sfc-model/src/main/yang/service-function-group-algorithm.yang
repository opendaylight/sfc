module service-function-group-algorithm {

  namespace "urn:cisco:params:xml:ns:yang:sfc-sfg-alg";

  prefix sfc-sfg-alg;

  import ietf-inet-types { prefix inet; }
  import ietf-yang-types { prefix yang; }

  organization "Contextream, Inc.";
  contact "Kfir Yeshayahu <kfir.yeshayahu@contextream.com>";


  description
    "This module contains a collection of YANG definitions for
     managing service function group algorithms.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2015-02-14 {
    description
    "Revised based on SFF Load Balance Feature Proposal";
  }

  grouping service-function-group-algorithm-entry {
      description
        "A list that holds all service function group algorithms in the domain";
      leaf name {
        type string;
        description
          "The name of the service function group algorithm";
      }
      leaf algorithm_type {
        type enumeration {
          enum ALL {
             value 0;
             description "Execute all buckets in the group. This group is used for multicast or broadcast
forwarding. The packet is effectively cloned for each bucket; one packet is processed for each
bucket of the group. If a bucket directs a packet explicitly out the ingress port, this packet clone
is dropped. If the controller writer wants to forward out the ingress port, the group must include
an extra bucket which includes an output action to the OFPP_IN_PORT reserved port";
          }
          enum SELECT {
             value 1;
             description "Execute one bucket in the group. Packets are processed by a single bucket in
the group, based on a switch-computed selection algorithm (e.g. hash on some user-configured
tuple or simple round robin). All configuration and state for the selection algorithm is external
to OpenFlow. The selection algorithm should implement equal load sharing and can optionally
be based on bucket weights. When a port specified in a bucket in a select group goes down, the
switch may restrict bucket selection to the remaining set (those with forwarding actions to live
ports) instead of dropping packets destined to that port. This behavior may reduce the disruption
of a downed link or switch";
          }
          enum INDIRECT {
             value 2;
             description "Execute the one defined bucket in this group. This group supports only
a single bucket. Allows multiple flow entries or groups to point to a common group identifier,
supporting faster, more efficient convergence (e.g. next hops for IP forwarding). This group type
is effectively identical to an all group with one bucket";
          }
          enum FAST_FAILURE {
             value 3;
             description "Execute the first live bucket. Each action bucket is associated with
a specific port and/or group that controls its liveness. The buckets are evaluated in the order
defined by the group, and the first bucket which is associated with a live port/group is selected.
This group type enables the switch to change forwarding without requiring a round trip to the
controller. If no buckets are live, packets are dropped.";
          }
        }
      }
  }

  typedef service-function-group-algorithm-ref {
    type leafref {
      path "/sfc-sfg-alg:service-function-group-algorithms/sfc-sfg-alg:service-function-group-algorithm/"
          + "sfc-sfg-alg:name";
    }
    description
      "This type is used by data models that need to reference
       configured service functions.";
  }

  // Service Function Group Algorithms

  container service-function-group-algorithms {
    description
      "All service function group algorithms";

    list service-function-group-algorithm {
      description
        "This list holds configuration data for all service function group algorithms
         in the domain";
      key "name";
      uses service-function-group-algorithm-entry;
    }
  }

// Remote procedure calls
}
