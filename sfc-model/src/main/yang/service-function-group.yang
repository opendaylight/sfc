module service-function-group {

  namespace "urn:cisco:params:xml:ns:yang:sfc-sfg";

  prefix sfc-sfg;

  import ietf-inet-types {
      prefix inet;
      revision-date 2013-07-15;
  }
  import service-function-group-algorithm {
      prefix sfc-sfg-alg;
      revision-date 2015-02-14;
  }
  import sfc-common {
      prefix sfc-common;
  }
  organization "Contextream, Inc.";
  contact "Kfir Yeshayahu <kfir.yeshayahu@contextream.com>";

  description
    "This module contains a collection of YANG definitions for
     managing service function group algorithms.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2015-02-14 {
    description
    "Revised based on SFF Load Balance Feature Proposal";
  }

  grouping service-function-group-entry {
      description
        "A list that holds all service function groups in the domain";
      leaf name {
        type string;
        description
          "The name of the service function group";
      }
      leaf groupId {
        type uint32;
        description
          "The groupId of the service function group";
      }
      leaf algorithm {
        type sfc-sfg-alg:service-function-group-algorithm-ref;
        mandatory true;
        description
          "The name of the service-function-group-algorithm used by this group";
      }
      leaf rest-uri {
        description "URI of REST based management";
        type inet:uri;
      }
      leaf ip-mgmt-address {
        type inet:ip-address;
        description
          "The IP and port used to configure this service-function";
      }
      leaf type {
        type sfc-common:sft-type-name;
        mandatory true;
        description
          "Service Function Type from service-function-type yang
           model";
      }
      list sfc-service-function {
        key "name";
        leaf name {
          type sfc-common:sf-name;
          description
            "The name of the Service Function";
        }
        description
          "A list of all service functions that are contained in this group";
      }

  }
  // Service Function Groups

  container service-function-groups {
    description
      "All service function groups";

   list service-function-group {
      description
        "This list holds configuration data for all service function groups
         in the domain";
      key "name";
      uses service-function-group-entry;
    }
  }

// Remote procedure calls
}
