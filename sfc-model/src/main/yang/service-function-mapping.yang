module service-function-mapping {

  namespace "urn:ericsson:params:xml:ns:yang:sfc-sf-map";

  prefix sfc-sf-map;

  import sfc-common {prefix sfc-common;}
  import service-function-type {prefix sfc-sft;}
  import service-locator {prefix sfc-sl;}
  import service-function {prefix sfc-sf;}
  import service-function-forwarder {prefix sfc-sff;}

  organization "Ericsson Inc.";
  contact "Brady Johnson <brady.allen.johnson@ericsson.com>";

  description
    "The defenitions herein allow for an SF and SFF to easily be
     identified given the Service Locator transport type and the
     SF type. These entities will be populated when the SFF and
     SFs are populated, and cannot be configured via RESTConf.
     Currently, there is no way of knowing if SFFs specified in
     adjacent Service Chain hops are reachable, so later, when
     SFC has something capable of determining the SFF topology,
     the SFF list may be modified.";

  revision 2014-07-01 {
    description
    "First version.";
  }

  container sff-dpl-by-sf-dpl-mappings {
      description "A mapping of SF-DPL to SFF-DPL.";
      list sff-dpl-by-sf-dpl-mapping {
          key "sf-dpl";
          leaf sf-dpl {
              type sfc-common:sf-data-plane-locator-name;
          }
          leaf sff-dpl {
              type sfc-common:sff-data-plane-locator-name;
          }
      }
  }

  container service-function-mapping {
    config false;
    description
      "This container maps the transport type to service function types
       that are reachable with the transport type. Each service function
       type then maps to a list of service functions of that type. Each
       service function then maps to a list of service function forwarders
       that can reach the service fuction with the transport type.";

    list sl-transports {
      key "transport";
      leaf transport {
        type identityref {
          base sfc-sl:sl-transport-type;
        }
        description
          "the name of the locator transport";
      }

      list service-function-types {
        key "sf-type";
        leaf sf-type {
          type sfc-common:sft-type;
          description
              "The service function type";
        }

        list service-functions {
          key "sf-name";
          leaf sf-name {
            type sfc-common:sf-name;
            description
              "the name of the service function";
          }

          list service-function-forwarders {
            key "sff-name";
            leaf sff-name {
              type sfc-common:sff-name;
              description
                "the name of the service function forwarder";
            }
          }
        }
      }
    }
  }
}
