module service-function-ovs {
  yang-version 1;

  namespace "urn:ericsson:params:xml:ns:yang:sfc-sf-ovs";

  prefix sfc-sf-ovs;

  import service-function {
      prefix sfc-sf;
      revision-date 2014-07-01;
      }
  import yang-ext {
      prefix ext;
      revision-date 2013-07-09;
      }

  organization "Ericsson, Inc.";
  contact "Brady Johnson <brady.allen.johnson@ericsson.com>";

  description
    "This module contains a collection of YANG definitions used
     to augment Service Function configuration with OpenvSwitch
     specific information.";

  revision 2016-01-07 {
    description
      "Augment SF to include OVS tap port in DPL.";
  }

  grouping connected-port {
    container ovs-port {
      leaf port-id {
        description "OVS port ID this SF is connected on.";
        type string;
      }
    }
  }

  augment "/sfc-sf:service-functions/"
        + "sfc-sf:service-function/"
        + "sfc-sf:sf-data-plane-locator/" {
    description
      "Augments the SF Data Plane Locator definition
       with OVS specific information";
    ext:augment-identifier "sf-dpl-ovs-augmentation";
    uses connected-port;
  }

}
