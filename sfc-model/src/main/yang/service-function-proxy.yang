module service-function-proxy{

  namespace "urn:intel:params:xml:ns:yang:sfc-sf-proxy";

  prefix sfc-sf-proxy;

  import service-locator {
    prefix sfc-sl;
    revision-date 2014-07-01;
  }

  import service-function {
    prefix sfc-sf;
    revision-date 2014-07-01;
  }

  import yang-ext {
    prefix ext;
    revision-date 2013-07-09;
  }

  organization "Intel, Inc.";
  contact "Hongjun Ni <hongjun.ni@intel.com>";

  description
    "This module contains a collection of YANG definitions used
     to augment Service Function configuration with
     proxy specific information.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC
     // publication and remove this note.

  revision 2016-01-25 {
    description "Augmentation of SF for proxy";
    reference "https://tools.ietf.org/html/draft-song-sfc-legacy-sf-mapping";
  }

  grouping proxy {
    container proxy-data-plane-locator {
      description "proxy's data-plane-locator";
      uses sfc-sl:data-plane-locator;
    }
  }

  augment "/sfc-sf:service-functions/"
        + "sfc-sf:service-function/"
        + "sfc-sf:sf-data-plane-locator" {
    description
      "Augments the SF data plane locator with
       proxy's data plane locator";
    ext:augment-identifier "sf-locator-proxy-augmentation";
    uses proxy;
  }
}
