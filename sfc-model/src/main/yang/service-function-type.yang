module service-function-type {

  namespace "urn:cisco:params:xml:ns:yang:sfc-sft";

  prefix sfc-sft;

  import service-locator {
      prefix sfc-sl;
      revision-date 2014-07-01;
  }

  import sfc-common {
      prefix sfc-common;
      revision-date 2015-10-17;
  }

  organization "Cisco Systems, Inc.";
  contact "Reinaldo Penno <repenno@cisco.com>";

  description
    "This module contains a collection of YANG definitions for
     managing service function types.

     It follows closely the constructs of
     http://tools.ietf.org/html/draft-ietf-netmod-interfaces-cfg-12

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC
     // publication and remove this note.

  revision 2014-07-01 {
    description
      "Changes based on Opendaylight Testing.";
    reference "https://tools.ietf.org/html/draft-penno-sfc-yang";
  }

  // Service Function Type definitions

  grouping service-function-type-definition {
    description
      "List of parameters to define an abstract type
       of Service Function";
    // TODO: Expand list to include metadata context
    // template support.
    // ie MD Type1 C3/C4 context, MD Type2 etc.
    leaf type {
      type sfc-common:sft-type-name;
      description
        "Service Function type names such as firewall,
         dpi, tcp-proxy, etc";
    }
    leaf bidirectional {
      type boolean;
      description "SF handles uplink and downlink traffic";
    }
    leaf nsh-aware {
      type boolean;
      description
        "Service Function can handle Network Service
         Headers";
    }
    leaf request-reclassification {
        type boolean;
        description "This leaf determines whether SF can request
          reclassification by the SFF";
    }
    leaf L2-transparent {
        type boolean;
        description "This leaf determines whether SF is L2 transparent i.e. do not change L2 addresses";
    }
    list supported-dataplanelocator-types {
      key "dataplanelocator-type";
      leaf dataplanelocator-type {
          type sfc-sl:sl-transport-type-def;
          description
            "Unique data plane identifier";
      }
      description
        "Data Plane Locator types from the Service
         Function";
    }
  }

  container service-function-types {
    description
      "A list of Service function Types. For each type we keep
       a list of Service Functions";

    list service-function-type {
      key "type";
      uses service-function-type-definition;

      list sft-service-function-name {
        // TODO: should this be sf-name typedef? Also this should be
        // kept in a separate map as an alternate index as it mirrors
        // state.
        key "name";
        leaf name {
          type sfc-common:sf-name;
          description
            "The name of the service function.";
        }
        description
          "The list of all service functions of a specific type";
      }
      description
        "A list of all service types. Each service-type entry holds
         a list of all service functions of that type";
    }
  }
}
