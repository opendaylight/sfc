module service-locator {

  namespace "urn:cisco:params:xml:ns:yang:sfc-sl";

  prefix sfc-sl;

  import ietf-inet-types {
      prefix inet;
      revision-date 2013-07-15;
  }
  import ietf-yang-types {
      prefix yang;
      revision-date 2013-07-15;
  }

  organization "Cisco Systems, Inc.";
  contact "Reinaldo Penno <repenno@cisco.com>";


  description
    "This module contains a collection of YANG definitions for
     managing service locators. Service locators are used as
     data plane network destinations for Service Functions and
     Service Function Forwarders

     It follows closely the constructs of
     http://tools.ietf.org/html/draft-ietf-netmod-interfaces-cfg-12

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC
     // publication and remove this note.

  revision 2014-07-01 {
    description
      "Changes based on Opendaylight Testing.";
    reference "https://tools.ietf.org/html/draft-penno-sfc-yang";
  }

  // Locator definitions

  // Transport type definitions
  identity transport-type {
    description
      "Base identity from which specific transport types are
       derived.";
  }

  identity mac {
    base "sl-transport-type";
    description "Simple MAC with optional VLAN transport type";
  }

  identity vxlan-gpe {
    base "sl-transport-type";
    description "Programmable vxlan GPE transport type";
  }

  identity vxlan {
    base "sl-transport-type";
    description "Programmable vxlan transport type";
  }

  identity gre {
    base "sl-transport-type";
    description "GRE transport type";
  }

  identity mpls {
    base "sl-transport-type";
    description "Multi Protocol Label Switching transport type";
  }

  identity other {
    base "sl-transport-type";
    description "unspecified transport type";
  }

  identity sl-transport-type {
    base "transport-type";
    description
      "This identity is used as a base for all transport
       types";

  }

  typedef sl-transport-type-def {
    type identityref {
      base "sl-transport-type";
    }
    description "This type is used to reference all
      registered transport types";
  }

  identity sfc-encapsulation-identity {
    description
      "Base identity from which the SFC encapsulation identities"
      + " are derived";
  }

  identity nsh {
    base "sfc-encapsulation-identity";
    description "SFC information is exchanged via NSH headers";
  }

  identity transport {
    base "sfc-encapsulation-identity";
    description "SFC information exchange is achieved by means of the transport";
  }

  identity mac-chaining {
      base "sfc-encapsulation-identity";
      description "SFC information exchange is achieved by means of the transport";
  }

  typedef sfc-encapsulation-type {
    type identityref {
        base "sfc-encapsulation-identity";
    }
    description "This type is used to reference all
      SFC encapsulation types";
  }

    grouping lisp-locator {
    description
      "Data plane-locator: Lisp Eid(IP)";
    leaf eid {
      type inet:ip-address;
      description "Data-plane IP address";
    }
  }

  grouping ip-port-locator {
    description
      "Data plane-locator: IP address and L4 port";
    leaf ip {
      type inet:ip-address;
      description "Data-plane IP address";
    }
    leaf port {
      type inet:port-number;
      description "Data-plane port number";
    }
  }

  grouping mac-address-locator {
    description
      "Data plane-locator: mac address and optional vlan-id";
    leaf mac {
      type yang:mac-address;
      description "Data-plane MAC address";
    }
    leaf vlan-id {
      type uint16 {
        range "1..4094";
      }
      description "Data-plane VLAN ID address";
    }
  }

  grouping mpls-locator {
    description
      "Data plane-locator: MPLS label";
    leaf mpls-label {
      type uint32 {
        range "1..1048575";
      }
      description "MPLS Label, 20 bits";
    }
  }

  grouping function-locator {
    description
      "When SF is co-located with SFF, this could be the name of a
       function or method.";
    leaf function-name {
      type string;
      description "Function or method name";
    }
  }

  grouping other-locator {
    description
      "Other locator";
    leaf other-name {
      type string;
      description "A other or undefined locator";
    }
  }

  grouping data-plane-locator {
    description
      "This group presents data-plane locator
       information for service function elements in the domain";
    choice locator-type {
      mandatory true;
      case ip {
        uses ip-port-locator;
      }
      case lisp {
        uses lisp-locator;
      }
      case mac {
        uses mac-address-locator;
      }
      case function {
        uses function-locator;
      }
      case mpls {
        uses mpls-locator;
      }
      case other {
        uses other-locator;
      }
      description "The collection of all possible data-plane
        locators. Only one can be chosen";
    }
    leaf transport {
      type identityref {
        base sfc-sl:sl-transport-type;
      }
      description
        "The encapsulation used to carry NSH packets";
    }
  }
}
