module service-node {

  namespace "urn:cisco:params:xml:ns:yang:sfc-sn";

  prefix sfc-sn;

  import ietf-inet-types {
      prefix inet;
      revision-date 2013-07-15;
      }
  import ietf-yang-types {
      prefix yang;
      revision-date 2013-07-15;
      }

  import sfc-common {
      prefix sfc-common;
      revision-date 2015-10-17;
      }


  organization "Cisco Systems, Inc.";
  contact "Reinaldo Penno <repenno@cisco.com>";


  description
    "This module contains a collection of YANG definitions for
     managing service function chains.

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-07-01 {
    description
      "Revision based on Opendaylight project feedback";
  }

  grouping service-node-grouping {
    description
      "This group bundle together the information that comprises
       a service-node";
    leaf name {
      type sfc-common:sn-name;
      description
        "The name of the service node";
    }
    leaf ip-mgmt-address {
      type inet:ip-address;
      description
        "The IP and port used to configure this service-node";
    }
    leaf-list service-function-forwarder {
      type sfc-common:sff-name;
      description
        "A list of service function forwarders resident in this
         service node";
    }
    leaf-list service-function {
      type sfc-common:sf-name;
      description
          "A list of service functions resident in this service
           node";
    }
  }

  container service-nodes {
    description
        "Physical or virtual element that hosts one or more service
         function forwarders";
    list service-node {
      key "name";
      uses service-node-grouping;
      description
        "The list that contains all service-nodes in the
         domain";
    }
  }
}
