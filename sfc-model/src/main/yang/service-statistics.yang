module service-statistics {

  namespace "urn:cisco:params:xml:ns:yang:sfc-ss";

  prefix sfc-ss;

  import ietf-inet-types {
      prefix inet;
      revision-date 2013-07-15;
      }

  import ietf-yang-types {
    prefix yang;
    revision-date 2013-07-15;
    }

  organization "Cisco Systems, Inc.";
  contact "Reinaldo Penno <repenno@cisco.com>";


  description
    "This module contains a collection of YANG definitions for
     managing service statistics. Service statistics are used
     to determine the load and efficiency of a service function
     or service function forwarder device

     Copyright (c) 2013 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

     // RFC Ed.: replace XXXX with actual RFC number and remove this
     // note.

     // RFC Ed.: update the date below with the date of RFC publication
     // and remove this note.

  revision 2014-07-01 {
    description
    "Initial Revision";
  }

  grouping service-statistics-group {
      list statistic-by-timestamp {
          key "timestamp";
          leaf timestamp {
              type uint64;
              description
                  "Date and time of record creation in milliseconds
                  counting from 1.1.1970 00:00:00 UTC (= 0)";
          }
          uses statistic-fields;
      }
  }

  grouping statistic-fields {
      container service-statistic {
          config false;
          leaf bytes-in {
            type yang:zero-based-counter64;
          }
          leaf bytes-out {
            type yang:zero-based-counter64;
          }
          leaf packets-in {
            type yang:zero-based-counter64;
          }
          leaf packets-out {
            type yang:zero-based-counter64;
          }
      }
  }
}
