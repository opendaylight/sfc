module sfc-of-renderer {
  yang-version 1;

  namespace "urn:ericsson:params:xml:ns:yang:sfc-of-renderer";
  prefix "sfcofrenderer";

  organization "Ericsson, Inc.";
  contact "Brady Johnson <brady.allen.johnson@ericsson.com>";

  revision 2015-11-23 {
    description
      "This module defines the SFC OpenFlow renderer configuration model.";
  }

  import sfc-common {
      prefix sfc-common;
      revision-date 2015-10-17;
  }

  container sfc-of-renderer-config {
    description
      "Configuration values for the SFC OpenFlow Renderer that are set
       in config subsystem";

    leaf sfc-of-table-offset {
      description
        "Used to offset pipeline to start at offset+1. Table0 is required.
        This allows the end-user to configure where the SFC pipeline starts.";
      type uint8;
    }

    leaf sfc-of-app-egress-table-offset {
      description
        "When SFC co-exists with other applications on the same OpenFlow
         switch, and the packets should be handed-off to the application
         instead of egressing them, this is the OpenFlow table to send the
         packets to for further processing.";
      type uint8;
    }
  }

  grouping sfc-of-tables-entry {
      leaf sff-name {
          type sfc-common:sff-name;
          description
             "The service function forwarder name these tables are on";
      }

      leaf base-table {
          type uint32;
      }
      leaf transport-ingress-table {
          type uint32;
      }
      leaf path-mapper-table {
          type uint32;
      }
      leaf path-mapper-acl-table {
          type uint32;
      }
      leaf next-hop-table {
          type uint32;
      }
      leaf transport-egress-table {
          type uint32;
      }
  }

  // The OpenFlow table offsets used by each SFF. Since an SFF may be
  // logical, or have application coexistence, its not always straight
  // forward to obtain the table offsets. This information will be used
  // mainly by RSP statistics. These offsets will be written to the
  // Operational data store upon RSP creation.
  container sfc-of-table-offsets {
      config false;

      description
        "Stores a list of the sfc openflow table offsets";

      list sfc-of-tables-by-base-table {
          key "sff-name";
          uses sfc-of-tables-entry;
      }
  }

}
