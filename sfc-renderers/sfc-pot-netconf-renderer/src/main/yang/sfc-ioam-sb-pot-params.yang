module sfc-ioam-sb-pot-params {

  yang-version 1;

  namespace "urn:cisco:params:xml:ns:yang:sfc-ioam-sb-pot-params";

  prefix sfc-ioam-sb-pot-params;

  import sfc-ioam-nb-pot {
      prefix ioam-nb-pot;
      revision-date 2016-11-22;
  }

  import sfc-ioam-sb-pot {
      prefix ioam-sb-pot;
      revision-date 2016-06-15;
  }

  organization "Cisco Systems, Inc.";
  contact
     "Srihari Raghavan <srihari@cisco.com>";

  description
    "This module contains a collection of YANG definitions for
     generated OAM proof of transit configuration
     parameters.";

  revision 2016-12-05 {
    description
      "Initial revision.";
    reference
      "";
  }

  container poly-parameters {
    config false;
    description "Proof of transit parameters.";

    uses ioam-nb-pot:refresh-period-interval;

    leaf profile-bit-mask-value {
      type ioam-nb-pot:bit-mask-options;
      description
        "Profile bit mask value used for proof of transit
         metadata calculations.";
    }

    leaf active-profile-index {
      type ioam-sb-pot:profile-index-range;
      description
        "Proof of transit profile index that is active.
         Will be set in the first hop of the path or chain.
         Other nodes will not use this field.";
    }

    list poly-parameter {
      key "pindex";
      ordered-by system;
      description
        "List of multiple algorithm parameters ordered
         by profile name for a node to use. For now, there are
         two profiles per RSP.";

      leaf pindex {
        type uint32;
        description
          "Profile index being referred to.";
      }

      leaf prime {
        type int64;
        description
          "Prime number value in the profile.";
      }

      list coeffs {
        ordered-by user;
        leaf coeff {
          type int64;
          description "Coefficient value.";
        }
        description
          "List of coefficients in the profile.";
      }

      list lpcs {
        ordered-by user;
        leaf lpc {
          type int64;
          description "LPC value";
        }
        description
          "List of LPCs in the profile being referred to.";
      }
    }
  }
}
