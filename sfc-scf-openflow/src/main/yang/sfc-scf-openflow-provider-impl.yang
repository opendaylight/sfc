// vi: set smarttab et sw=4 tabstop=4:
module sfc-scf-openflow-provider-impl {

  yang-version 1;
  namespace "urn:opendaylight:params:xml:ns:yang:controller:config:sfc-scf-openflow-provider:impl";
  prefix "sfc-scf-openflow-provider-impl";

  import config { prefix config; revision-date 2013-04-05; }
  import rpc-context { prefix rpcx; revision-date 2013-06-17; }
  import opendaylight-md-sal-binding { prefix mdsal; revision-date 2013-10-28; }


  description
      "This module contains the base YANG definitions for
      sfc-scf-ofrenderer impl implementation.";

  revision "2014-09-01" {
      description
          "Initial revision.";
  }

  // This is the definition of the service implementation as a module identity
  identity sfc-scf-openflow-provider-impl {
      base config:module-type;

      // Specifies the prefix for generated java classes.
      config:java-name-prefix SfcScfOfRenderer;
  }


  // Augments the 'configuration' choice node under modules/module.
  augment "/config:modules/config:module/config:configuration" {
    case sfc-scf-openflow-provider-impl {
      when "/config:modules/config:module/config:type = 'sfc-scf-openflow-provider-impl'";

      //wires in the data-broker service
      container data-broker {
        uses config:service-ref {
          refine type {
              mandatory false;
              config:required-identity mdsal:binding-async-data-broker;
          }
        }
      }

      container notification-service {
        uses config:service-ref {
          refine type {
            mandatory true;
            config:required-identity mdsal:binding-notification-service;
          }
        }
      }

      container rpc-registry {
        uses config:service-ref {
          refine type {
             mandatory true;
             config:required-identity mdsal:binding-rpc-registry;
          }
        }
      }
    }
  }
}
