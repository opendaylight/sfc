module sfc-test-consumer-impl {

    yang-version 1;
    namespace "urn:opendaylight:params:xml:ns:yang:controller:config:sfc-test-consumer:impl";
    prefix "sfc-test-consumer-impl";

    import config { prefix config; revision-date 2013-04-05; }
    import rpc-context { prefix rpcx; revision-date 2013-06-17; }

    import opendaylight-md-sal-binding { prefix mdsal; revision-date 2013-10-28; }

    description
        "This module contains the base YANG definitions for
        test-consumer impl implementation.";

    revision "2014-07-01" {
        description
            "Initial revision.";
    }

    // This is the definition of test-consumer interface identity.
    identity sfc-test-consumer {
        base "config:service-type";
        config:java-class "org.opendaylight.sfc.sfc_test_consumer.SfcTestConsumer";
    }

    // This is the definition of test-consumer implementation module identity.
    identity sfc-test-consumer-impl {
            base config:module-type;
            config:provided-service sfc-test-consumer;
            config:java-name-prefix SfcTestConsumer;
    }

    augment "/config:modules/config:module/config:configuration" {
        case sfc-test-consumer-impl {
            when "/config:modules/config:module/config:type = 'sfc-test-consumer-impl'";

            container rpc-registry {
                uses config:service-ref {
                    refine type {
                        mandatory true;
                        config:required-identity mdsal:binding-rpc-registry;
                    }
                }
            }
        }
    }
    augment "/config:modules/config:module/config:state" {
        case sfc-test-consumer-impl {
            when "/config:modules/config:module/config:type = 'sfc-test-consumer-impl'";

            rpcx:rpc-context-instance "test-a-put-sf-rpc";
            rpcx:rpc-context-instance "test-a-read-sf-rpc";
            rpcx:rpc-context-instance "test-a-delete-sf-rpc";

            rpcx:rpc-context-instance "test-b-put-sfs-rpc";
            rpcx:rpc-context-instance "test-b-put-sfc-rpc";
            rpcx:rpc-context-instance "test-b-read-sfc-rpc";
            rpcx:rpc-context-instance "test-b-delete-sfc-rpc";

            rpcx:rpc-context-instance "test-c-put-data-rpc";
        }
    }

    identity test-a-put-sf-rpc;

    rpc test-a-put-sf  {
        description
          "Shortcut JMX call for testing.";

        input {
            uses rpcx:rpc-context-ref {
                refine context-instance {
                    rpcx:rpc-context-instance test-a-put-sf-rpc;
                }
            }
        }
        output {
            leaf result {
                type boolean;
            }
        }
    }

    identity test-a-read-sf-rpc;

    rpc test-a-read-sf  {
        description
          "Shortcut JMX call for testing.";

        input {
            uses rpcx:rpc-context-ref {
                refine context-instance {
                    rpcx:rpc-context-instance test-a-read-sf-rpc;
                }
            }
        }
        output {
            leaf result {
                type boolean;
            }
        }
    }

    identity test-a-delete-sf-rpc;

    rpc test-a-delete-sf  {
        description
          "Shortcut JMX call for testing.";

        input {
            uses rpcx:rpc-context-ref {
                refine context-instance {
                    rpcx:rpc-context-instance test-a-delete-sf-rpc;
                }
            }
        }
        output {
            leaf result {
                type boolean;
            }
        }
    }

    identity test-b-put-sfs-rpc;

    rpc test-b-put-sfs  {
        description
          "Shortcut JMX call for testing: creating a set of SFs";

        input {
            uses rpcx:rpc-context-ref {
                refine context-instance {
                    rpcx:rpc-context-instance test-b-put-sfs-rpc;
                }
            }
        }
        output {
            leaf result {
                type boolean;
            }
        }
    }

    identity test-b-put-sfc-rpc;

    rpc test-b-put-sfc {
        description
          "Shortcut JMX call for testing: creating SFC";

        input {
            uses rpcx:rpc-context-ref {
                refine context-instance {
                    rpcx:rpc-context-instance test-b-put-sfc-rpc;
                }
            }
        }
        output {
            leaf result {
                type boolean;
            }
        }
    }

    identity test-b-read-sfc-rpc;

    rpc test-b-read-sfc {
        description
          "Shortcut JMX call for testing:reading SFC";

        input {
            uses rpcx:rpc-context-ref {
                refine context-instance {
                    rpcx:rpc-context-instance test-b-read-sfc-rpc;
                }
            }
        }
        output {
            leaf result {
                type boolean;
            }
        }
    }

    identity test-b-delete-sfc-rpc;

    rpc test-b-delete-sfc {
        description
          "Shortcut JMX call for testing: deleting SFC";

        input {
            uses rpcx:rpc-context-ref {
                refine context-instance {
                    rpcx:rpc-context-instance test-b-delete-sfc-rpc;
                }
            }
        }
        output {
            leaf result {
                type boolean;
            }
        }
    }

    identity test-c-put-data-rpc;

    rpc test-c-put-data {
        description
          "Shortcut JMX call for testing: creating all data";

        input {
            uses rpcx:rpc-context-ref {
                refine context-instance {
                    rpcx:rpc-context-instance test-c-put-data-rpc;
                }
            }
        }
        output {
            leaf result {
                type boolean;
            }
        }
    }
}
