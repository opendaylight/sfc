// vi: set smarttab et sw=4 tabstop=4:
module sfc-ofrenderer-impl {

  yang-version 1;
  namespace "urn:opendaylight:params:xml:ns:yang:controller:config:sfc-ofrenderer:impl";
  prefix "sfc-ofrenderer-impl";

  import config { prefix config; revision-date 2013-04-05; }
  import rpc-context { prefix rpcx; revision-date 2013-06-17; }
  import opendaylight-md-sal-binding { prefix mdsal; revision-date 2013-10-28; }


  description
      "This module contains the base YANG definitions for
      sfc-ofrenderer impl implementation.";

  revision "2016-05-12" {
      description
          "Initial revision. Based on sfc-l2renderer-impl@2014-09-01";
  }

  // This is the definition of the service implementation as a module identity
  identity sfc-ofrenderer-impl {
      base config:module-type;

      // Specifies the prefix for generated java classes.
      config:java-name-prefix SfcOfRenderer;
  }


  // Augments the 'configuration' choice node under modules/module.
  augment "/config:modules/config:module/config:configuration" {
    case sfc-ofrenderer-impl {
      when "/config:modules/config:module/config:type = 'sfc-ofrenderer-impl'";

      //wires in the data-broker service
      container data-broker {
        uses config:service-ref {
          refine type {
              mandatory false;
              config:required-identity mdsal:binding-async-data-broker;
          }
        }
      }

      container notification-service {
        uses config:service-ref {
          refine type {
            mandatory true;
            config:required-identity mdsal:binding-notification-service;
          }
        }
      }

      container rpc-registry {
        uses config:service-ref {
          refine type {
             mandatory true;
             config:required-identity mdsal:binding-rpc-registry;
          }
        }
      }
    }
  }
}
